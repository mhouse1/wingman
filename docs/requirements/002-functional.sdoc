[DOCUMENT]
TITLE: Wingman Functional Requirements
UID: DOC-FR
PREFIX: FR-

[TEXT]
STATEMENT: >>>
Functional behaviour of MetalStorm Wingman: the FSM contract, mission
lifecycle, and timing bounds. The replay path YAML
(tests/replay_paths/adr037_paths.yaml) remains the source of truth for FSM
acceptance criteria; requirements here point at it and do not re-encode it.
<<<

[REQUIREMENT]
UID: FR-001
TITLE: Game-state FSM contract
STATEMENT: >>>
Wingman shall model the game session as a finite state machine with the
states GAME_UNKNOWN, GAME_LOBBY, GAME_WAITING, GAME_STARTING,
GAME_STARTING_STALLED, GAME_BATTLE, GAME_BATTLE_MANUAL, GAME_BATTLE_EJECT
and GAME_END_B, whose transition sequence for the standard mission loop is
validated per tick by the runtime replay gate.
<<<
RATIONALE: >>>
The executable criterion is tests/replay_paths/adr037_paths.yaml
(expected_state, expected_trigger, max_settle_time_s per step), enforced by
make rr-path1-gate (ADR 044) and the live-screen lane (ADR 045).
<<<

[REQUIREMENT]
UID: FR-002
TITLE: Tick cadence and non-blocking OCR
STATEMENT: >>>
The main loop shall process one captured frame per tick at the cadence
configured by loop_interval_sec, and OCR work shall run asynchronously such
that a tick never blocks on OCR completion. Per-crop OCR timings shall be
recorded per session and compared against the release baseline using the
thresholds in config.yaml.
<<<
RATIONALE: >>>
The performance regression workflow: PerformanceTracker histograms per crop,
docs/performance/current vs release, make tp preview gates.
<<<

[REQUIREMENT]
UID: FR-003
TITLE: Mission launch after Good Luck
STATEMENT: >>>
On detecting the Good Luck banner in GAME_STARTING, wingman shall launch the
mission after at most mission.good_luck_wait_s, and earlier when battle-alive
evidence is confirmed while mission.good_luck_bypass_on_alive is enabled.
Whether the wait ran its full length or was bypassed shall be logged.
<<<
RATIONALE: >>>
ADR 065: the wait is the no-evidence fallback; the bypass converts confirmed
health evidence into earlier launches (measured mean saving 3.9 s per launch
across 54 armed windows in three sessions).
<<<

[REQUIREMENT]
UID: FR-004
TITLE: Battle entry on confirmed battle-alive evidence
STATEMENT: >>>
Wingman shall enter the battle within 1.0 s of the first confirmed
battle-alive indication during GAME_STARTING.
<<<
RATIONALE: >>>
Bound settled 2026-08-07 from three live sessions (54 armed windows, 40
first-raw-read measurements): once battle-alive is confirmed, the Good-Luck
wait polls at 0.1 s, so 1.0 s is comfortably satisfiable. The ~1.5 s
confirmation latency measured in those sessions is upstream of "first
confirmed indication" and does not count against this bound. ADR 032 designed
the fallback; ADR 065 made it reachable.
<<<

[REQUIREMENT]
UID: FR-004.1
TITLE: Battle-alive probe observability
STATEMENT: >>>
The GAME_STARTING battle-alive probe shall log every attempt, including
attempts that read no value, and shall report attempt count and
first-raw-read time on disarm.
<<<
RATIONALE: >>>
ADR 065 Decision 4. The probe was unreachable for three months because a
probe that never ran and a probe that ran and saw nothing produced identical
logs: silence. This requirement is what makes FR-004 falsifiable in
production.
<<<
RELATIONS:
- TYPE: Parent
  VALUE: FR-004

[REQUIREMENT]
UID: FR-005
TITLE: Aircraft remains inside the battle arena
STATEMENT: >>>
During GAME_BATTLE, wingman shall continuously steer the aircraft toward
detected enemy positions, so that the aircraft does not fly outside the
battle arena.
<<<
RATIONALE: >>>
ADR 028 (minimap ring-engage navigation). The preprogrammed mission path
sometimes carried the aircraft outside the battle area. Enemies only render
inside the arena, so navigation that always steers toward detected enemies
bounds the excursion. No arena-boundary sensor exists; the requirement is
verified by outcome (excursion observations with ring-engage on vs off).
Implemented by EngageNavigator.update (wingman/engage_nav.py).
<<<

[REQUIREMENT]
UID: FR-006
TITLE: Evasive manoeuvre on incoming missile detection
STATEMENT: >>>
When an incoming-missile detection is present during GAME_BATTLE and the
missile-evade tactic is enabled, wingman shall hold afterburner, roll-right
and yaw-left simultaneously. The hold shall release when no fresh incoming
detection has been observed for behavior_tree.missile_evade.clear_seconds,
or when the hold has lasted behavior_tree.missile_evade.max_manoeuvre_s,
whichever occurs first; the manoeuvre-limit release applies even while a
detection is still present. A repeated detection reading whose cache
timestamp has not advanced shall not count toward clearance. The manoeuvre
shall take selection priority over engage navigation and shall yield to
eject and respawn handling.
<<<
RATIONALE: >>>
ADR 070. Flares alone against a missile on a non-manoeuvring target is the
weakest case for a countermeasure; the evade denies the missile a steady
intercept solution while the existing flare burst (FR: flare deployment path,
unchanged) decoys the seeker. Selection priority in the ADR 024 behavior tree
provides the mutual exclusion with engage geometry and eject. The
manoeuvre-limit release is ADR 070 d12: the tactic is a tactical window, not
a hold-until-clear — past it the manoeuvre only bleeds energy (the V2
zoom-climb evidence), and under sustained barrages the limit, not clearance,
is the modal exit. SAF-006's unconditional cap remains the fault backstop
above both release paths.
<<<

[REQUIREMENT]
UID: FR-007
TITLE: Operating-altitude climb and low-altitude recovery
STATEMENT: >>>
At mission start, and at each mission restart after a respawn, wingman shall
command a climb and shall not begin search-and-destroy until a fresh
telemetry altitude at or above behavior_tree.climb.mission_start_alt has
been confirmed, the altitude is unreadable, or a duration budget of
behavior_tree.climb.mission_start_max_s has elapsed. Independently, during
GAME_BATTLE, when behavior_tree.climb.confirm_reads consecutive fresh
altitude readings fall below behavior_tree.climb.enter_below_alt, wingman
shall command a climb until the same number of consecutive fresh readings
reach behavior_tree.climb.exit_above_alt. A climb shall apply pitch input in
bounded pulses, re-applied only while the observed climb rate is below
behavior_tree.climb.min_climb_rate; it shall take selection priority over
engage navigation and shall yield to eject, missile evade, respawn handling,
and manual takeover, both at climb start and while a climb is in progress.
<<<
RATIONALE: >>>
ADR 073. A mid-mission respawn used to leave the aircraft flying level at
spawn altitude — below the navigator's safe floor nothing steered, and the
observed outcome was terrain impact. The operating-altitude prologue and the
emergency band close that gap as an invariant ("be high") rather than a
scripted step. Pulsed pitch is the 3.2c live finding: a continuously held
nose-up input loops the airframe (altitude oscillated with zero net gain for
a full minute), so pitch is re-applied only while the climb rate is
deficient. Confirmed readings guard both band edges because single garbage
OCR stable-values were observed entering the band mid-flight. Yield ordering
is the ADR 070 d11 pattern: selection priority orders selections, not thread
lifetimes, so the climb hold also polls the higher-priority tactics' running
state. Implemented by Controller.climb_mode (wingman/controller.py).
<<<

[REQUIREMENT]
UID: FR-008
TITLE: Afterburner held during an incoming-missile alert
STATEMENT: >>>
While an incoming-missile detection is present, wingman shall hold the
afterburner input, and shall release it only once no incoming detection has
been observed for missile_evade.afterburner_clear_s. A detection observed
while the hold is already active shall extend the hold rather than start a
second one. The hold shall be bounded by an absolute duration of
missile_evade.afterburner_max_s, after which it shall release and record
that the alert was still present. Flare deployment on a new incoming
detection shall be unaffected by the hold.
<<<
RATIONALE: >>>
ADR 128. Flares change what the missile is tracking; speed changes whether it
can still reach the aircraft, and the two are complementary rather than
alternative. The release is keyed on the alert going quiet rather than on a
fixed burn time because the alert's duration is what indicates the threat is
still live. The hold is bounded twice — by the quiet deadline and by an
absolute cap — because the afterburner key is not a watched maneuver key, so
a stuck press would not surface as a manual takeover; it would simply be a
throttle nobody could release. Implemented by
Controller._start_afterburner_evade (wingman/controller.py).
<<<

[REQUIREMENT]
UID: FR-009
TITLE: Hotkey mission restart survives standby's own exit flag
STATEMENT: >>>
After the operator's first Backspace has placed wingman into standby, a
mission started by the configured-mission hotkey shall run until the operator
cancels it, until it completes on its own, or until a genuine program exit
occurs; it shall not be aborted by the exit-request signal that entering
standby itself leaves set. A program exit that occurs without the operator
having pressed Backspace — SIGTERM, or the startup-stall exit — shall still
abort a running mission as before.
<<<
RATIONALE: >>>
ADR 130. Standby exists so the operator can restart the mission by hand while
MetalStorm stays up, but the exit-request flag that breaks the main loop into
standby is never cleared afterward. A mission's own abort check could not tell
"we are exiting" from "we already finished exiting, into standby" — so every
hotkey-started mission read the stale flag on its first poll and self-cancelled
within about 50 ms, measured directly in wingman.log across nine consecutive
attempts. Implemented by Controller._mission_exit_requested
(wingman/controller.py), which distinguishes the two cases using the flag
Backspace alone sets (ADR 099).
<<<

[REQUIREMENT]
UID: FR-010
TITLE: Nested display closes with the game
STATEMENT: >>>
On an operator-initiated stop — the finish-round-then-exit hotkey, or the
second of the two-stage Backspace sequence — wingman shall close the nested
Xwayland display together with MetalStorm, gated on
finish_round_then_exit.close_game. If MetalStorm exits on its own, wingman
shall close the nested display regardless of close_game. A termination
signal that reaches wingman shall route through this same teardown rather
than bypass it. An operator-initiated close request that has already
arrived by the time an unrelated interrupt is handled shall not be
discarded by that interrupt's handling.
<<<
RATIONALE: >>>
ADR 099 D6 and ADR 105 D6. The nested server exists solely to host the game;
leaving it behind strands an empty "Xwayland on :N" window on the operator's
desktop, invisible to the operator unless they go looking for it. Two gaps
found live 2026-09-08 motivate the last two sentences: an unhandled SIGHUP
(a closed controlling terminal) terminated wingman with no cleanup at all,
skipping this teardown entirely; separately, a SIGINT racing the second
Backspace could win the standby wait loop by about a millisecond, and the
interrupt handler discarded the already-arrived close request unconditionally
instead of checking for it. Both left the display orphaned after the game had
already exited. Implemented by close_nested_display
(wingman/game_shutdown.py); the signal routing and the interrupt/close-request
race are in wingman/main.py (the SIGTERM/SIGHUP handlers near the top of
main(), and the standby KeyboardInterrupt handler).
<<<

[REQUIREMENT]
UID: FR-011
TITLE: Roll-right held through the flares on an incoming-missile alert
STATEMENT: >>>
When a new incoming-missile detection triggers a flare burst during
GAME_BATTLE or GAME_BATTLE_EJECT, wingman shall hold roll-right from the
detection until behavior_tree.missile_evade.flare_roll_after_s after the
burst's last flare has been deployed. A detection that triggers another
burst while the roll is held shall extend the hold to the same interval
after that burst's last flare, rather than start a second hold. The roll
shall be held whether or not the missile-evade tactic (FR-006) is enabled
or flying. While it is held, the pursuit's steering shall write neither
pitch nor roll, so the roll leaves the flight path unchanged. The hold
shall end on manual takeover, on program exit, when an eject begins, and
when a hard-emergency climb takes the airframe, and in any case no later
than behavior_tree.missile_evade.flare_roll_max_s after it began.
<<<
RATIONALE: >>>
Operator, 2026-10-27; ADR 164. The roll is a continuous barrel roll about
the aircraft's own axis: it does not change the trajectory, it keeps the
aircraft turning about that axis, which makes it harder for a missile to
hit. The flight path stays unchanged only if nothing else steers while it
rolls, hence the pursuit's yield. flare_roll_after_s ships at the
operator's 2 s. The behaviour existed before and was lost twice: the
March 2026 mission_j20 script rolled right while it dropped flares, and
went with the scripted missions; ADR 070's evade held roll-right on every
alert in GAME_BATTLE, but once the pursuit took over the fights the tree no
longer acts there, and the evade ran in 4 of 434 alerted missile kills
(Research 019). This requirement exists so that it is not lost a third
time. Its ends are the ones every held flight key has: SAF-001's takeover,
SAF-007's exit, ADR 070 d11's eject, and ADR 163 D5's hard emergency,
whose pull-up a roll would turn sideways. The cap is a fault backstop for
a burst that never reports its last flare. Implemented by
Controller.flare_roll (wingman/controller.py), started from
AmmoEventsHandler.deploy_flares_on_new_incoming (wingman/tick_handlers.py);
pinned by tests/test_flare_roll.py.
<<<
