[DOCUMENT]
TITLE: Wingman Safety Requirements
UID: DOC-SAF
PREFIX: SAF-

[TEXT]
STATEMENT: >>>
Safety properties of MetalStorm Wingman. The recurring hazard across ADRs 058,
059, 061, 063 and 064 is uncommanded flight: wingman issuing or continuing
flight-control input when the operator, or the game state, says it must not.
Each requirement states the property only; the governing ADR is referenced for
rationale and evidence. Tuning values live in wingman/config.yaml, never here.
<<<

[REQUIREMENT]
UID: SAF-001
TITLE: Operator flight-control input preempts commanded flight
STATEMENT: >>>
When the operator physically presses a takeover key — the dedicated
MANUAL_TAKEOVER_KEY, an arrow key, or a flight-control key (NOSE_UP i,
NOSE_DOWN k, ROLL_LEFT j, ROLL_RIGHT l) on a display wingman does not inject
into — while wingman is
commanding flight — a mission thread holds the mission lock, an eject
sequence is active, or a tactic hold (climb, missile evade) is active —
wingman shall cease all commanded flight input, including the tactic hold
threads, within 2.0 s and transition to GAME_BATTLE_MANUAL, and shall not
re-command flight until health evidence indicates a death and respawn, or,
for a takeover by MANUAL_TAKEOVER_KEY, until the round ends (SAF-001.4).
<<<
RATIONALE: >>>
**Amended 2026-10-30 — a takeover by Enter holds until the round ends
(SAF-001.4).** The operator asked for Enter to take the aircraft and keep it
through respawns until the round exits. The other takeover keys keep the
respawn return below.

**Amended 2026-08-30 — the takeover keys the operator must use depend on where
they press them.** On the ADR 099 nested display lane wingman injects into the
same X display it observes, so its own i/j/k/l presses and the operator's are
indistinguishable in content. Telling them apart by ARRIVAL time was measured
failing: under 13 OCR workers echoes arrived 1.67-9.74 s after release against a
1.0 s grace window, producing four spurious takeovers in 23 minutes, each
dropping the aircraft out of automation mid-round. Widening the grace is not
available — it would suppress the operator's own presses for the same seconds,
against the 2.0 s bound below.

Takeover at the game window is therefore by keys wingman NEVER injects: the
dedicated MANUAL_TAKEOVER_KEY (Enter, chosen for size — a control reached for
in a hurry should be found without looking) and the arrow keys. i/j/k/l retain
their meaning on the operator's own display, where wingman injects nothing,
with the ctrl+alt modifier that keeps ordinary typing from flying the aircraft.

Control returns to wingman on a respawn, resuming the last mission flown, and
on the operator's explicit request with MISSION_J20_KEY ('u') — the key already
used for this in GAME_BATTLE. 'u' is a key wingman injects itself, so it is
delivered on the injection display only while the takeover is active, where
wingman injects nothing but flares and there is nothing it could be confused
with.

Persisting the takeover across deaths was tried on 2026-08-30 and reverted the
same day: the operator hit two deaths inside one takeover, each needing a
keypress before wingman would fly again, which makes an unattended session need
attending. The behaviour remains available as
`mission.manual_takeover.persist_through_respawn`.

The cost is honest: a reflexive grab of i/j/k/l at the game window no longer
yields control on its own. A server-timestamp discriminator would restore that
— X key events carry the server's own timestamp, immune to delivery latency —
but it needs a clock calibration that fails silently back to the spurious
takeovers, which is a worse failure than an extra keypress.

The manual-takeover guarantee. The 2.0 s cessation bound is enforced by
tests/test_mission_cancel.py::test_cancel_releases_lock_within_two_seconds.
Requested 2026-08-07; behaviour shipped in wingman/controller.py
(_handle_maneuver_key_press). ADR 059 governs the post-death return to auto.
Tactic holds added 2026-08-17: a live session showed the FSM transitioning
to GAME_BATTLE_MANUAL while the climb hold kept pulsing nose-up and cycling
the afterburner for the rest of its 90 s cap — the transition alone does not
stop the hold threads, so takeover must stop them explicitly and the holds
must release when the FSM leaves their owning states.
<<<

[REQUIREMENT]
UID: SAF-001.1
TITLE: Injected key presses never trigger takeover
STATEMENT: >>>
Wingman's own injected key presses, including X-server auto-repeat echoes
delivered after release, shall never trigger the manual-takeover path.
<<<
RATIONALE: >>>
Injected keys echo back through the XRecord listener at a measured ~25 Hz
(ADR 053). Without echo discrimination, every eject correction would trigger
its own takeover.
<<<
RELATIONS:
- TYPE: Parent
  VALUE: SAF-001

[REQUIREMENT]
UID: SAF-001.2
TITLE: Entry grace window for stale keystrokes
STATEMENT: >>>
Physical flight-control presses within the 2.0 s grace window after
GAME_BATTLE or GAME_BATTLE_EJECT entry shall be ignored, and the ignored
press shall be logged when the exception is exercised. The window does not
apply to MANUAL_TAKEOVER_KEY (SAF-001.4).
<<<
RATIONALE: >>>
Stale-keystroke protection: keystrokes queued during a state transition must
not flip the aircraft into manual mode the instant a battle begins. Wingman
never injects MANUAL_TAKEOVER_KEY, so a press of it is never stale.
<<<
RELATIONS:
- TYPE: Parent
  VALUE: SAF-001

[REQUIREMENT]
UID: SAF-001.3
STATUS: Draft
TITLE: The takeover-key listener stays able to hear keys
STATEMENT: >>>
On the display wingman injects into, if a reporting interval of the
takeover-key listener passes in which wingman injected key presses on that
display but the listener received none, wingman shall log the condition and
re-establish the listener before the end of the next reporting interval.
<<<
RATIONALE: >>>
SAF-001's takeover at the game window depends on a listener that hears keys.
On 2026-09-26, 3 of 21 sessions had the nested-display listener hear nothing
for the whole session, from the start, with no error logged, and an ENTER
typed into the game window did not reach the takeover path. Wingman's own
injected presses on that display give the liveness signal. Design 009,
"A deaf hotkey listener on the nested display".
<<<
RELATIONS:
- TYPE: Parent
  VALUE: SAF-001

[REQUIREMENT]
UID: SAF-001.4
STATUS: Draft
TITLE: A takeover by MANUAL_TAKEOVER_KEY holds until the round ends
STATEMENT: >>>
When the operator presses MANUAL_TAKEOVER_KEY (Enter) in GAME_BATTLE,
GAME_BATTLE_EJECT or GAME_BATTLE_MANUAL, wingman shall be in GAME_BATTLE_MANUAL
whether or not it was commanding flight, and shall stay there through every
respawn, without re-commanding flight, until the game state leaves the battle
states or the operator presses the handback key (MISSION_J20_KEY, 'u'). When the
operator presses it in GAME_STARTING, GAME_STARTING_STALLED or GAME_UNKNOWN,
wingman shall start no mission for the coming round and shall enter
GAME_BATTLE_MANUAL, under the same hold, when that round reaches GAME_BATTLE;
the claim ends if the state reaches GAME_LOBBY, GAME_WAITING or GAME_END_B first.
<<<
RATIONALE: >>>
**Amended 2026-11-01 — Enter works from the countdown on, with no entry grace.**
From 2026-10-30 to 2026-11-01, 24 of 73 Enter presses were dropped, and 21 of
those were followed by another press within 20 s. 12 fell in the entry grace, 11
of them within 2 s of entering battle; 8 fell in the Good Luck countdown and 2 in
the GAME_UNKNOWN after a stall. The operator reaches for Enter as a round starts,
so those are the seconds it most has to work. The grace was kept for this key
against an Enter queued from lobby chat, which no log shows: wingman never
injects Enter, and battle entry follows the lobby by at least the Good Luck wait.

Operator, 2026-10-30: "when pressed it should enter manual and stay in manual
mode until the round exits, respawn should not kick it out of manual". Enter is
the deliberate "I fly this round" key; i/j/k/l and the arrow keys keep SAF-001's
return on respawn, so a reflexive grab still hands the aircraft back after a
death and an unattended session does not need attending (the 2026-08-30
experiment). In GAME_LOBBY and GAME_WAITING Enter is ordinary input (lobby chat).
The handback key stays the operator's way out. Rounds flown this way carry
manual_takeover_count above 0, and Design 018 charts them apart from wingman's
own.
<<<
RELATIONS:
- TYPE: Parent
  VALUE: SAF-001

[REQUIREMENT]
UID: SAF-002
TITLE: No commanded flight while the aircraft is dead
STATEMENT: >>>
Wingman shall not issue flight-control input while health evidence indicates
the aircraft is not alive, and shall restart the mission only after health
evidence confirms the aircraft is alive again. This holds in every battle
state, including GAME_BATTLE_MANUAL and GAME_BATTLE_EJECT.
<<<
RATIONALE: >>>
The uncommanded-flight incident class: three separate production incidents
(missed-overlay respawn, manual-mode death, eject flying straight) reduced to
wingman commanding a dead or respawned aircraft. ADR 059 (single restart
path), ADR 061 (observed-death provenance).
<<<

[REQUIREMENT]
UID: SAF-003
TITLE: Every respawn is handled exactly once
STATEMENT: >>>
Every death-and-respawn episode shall trigger respawn handling exactly once:
by overlay OCR when it detects the episode, otherwise by the health-evidence
fallback. The fallback shall stand down when OCR owns the episode, so that no
episode is handled twice and no episode is dropped.
<<<
RATIONALE: >>>
ADR 064 dual-sensor design. Overlay OCR recall is ~92%; the health fallback
covers the misses (first live catch: 2026-08-07 08:12, tier=strong,
dead_for=4.6 s, OCR at 0% confidence). The recent-OCR-edge stand-down window
prevents double-firing. Scored per session in the respawn_shadow stats block.
<<<

[REQUIREMENT]
UID: SAF-004
TITLE: Unconfirmed health reads are never acted upon
STATEMENT: >>>
A raw health OCR read shall not change wingman's alive/dead state until it is
confirmed by recurrence: two of the last three reads agreeing within the
configured tolerance (health.value_confirm_window, value_confirm_tolerance).
Reads above health.max_plausible shall be discarded outright.
<<<
RATIONALE: >>>
ADR 063. A logged session measured roughly 50% garbage reads (fragments,
concatenations, a false 0) over the respawn overlay; acting on any single
read produced spurious death/respawn transitions.
<<<

[REQUIREMENT]
UID: SAF-005
TITLE: Bounded nose-down command during eject
STATEMENT: >>>
Cumulative commanded nose-down during a single eject sequence shall not
exceed telemetry.eject_closed_loop.total_nose_budget_s. A climb observed
after a continuous nose-down hold longer than over_rotation_after_s shall
release the hold rather than re-issue it.
<<<
RATIONALE: >>>
ADR 058 d12. Across 27 logged ejects the productive descent happened in the
first ~8-11 s of hold; holding longer over-rotated the aircraft into a climb
— commanded input producing the opposite of the commanded intent.
<<<

[REQUIREMENT]
UID: SAF-006
TITLE: Bounded missile-evade hold
STATEMENT: >>>
A missile-evade hold shall release all held flight keys unconditionally no
later than behavior_tree.missile_evade.max_hold_s after entry, and shall
release them on program exit and on controller cleanup. Absence of fresh
perception samples shall not end the hold early, and shall not extend it past
the cap.
<<<
RATIONALE: >>>
ADR 070 d6. A detection stuck true (a HUD element that keeps matching the
template, a frozen frame) would otherwise pin afterburner and a
full-deflection roll for the rest of the mission and fly the aircraft out of
the arena — the same failure class as the ADR 069 nose-hold budget. The cap
firing is a detector fault and is logged at WARNING.
<<<

[REQUIREMENT]
UID: SAF-007
TITLE: No injected key survives process termination
STATEMENT: >>>
On termination — normal exit, SIGTERM, or controller cleanup — wingman shall
release every key it is capable of injecting, such that no wingman-injected
key press remains asserted in the X server after the wingman process has
exited. This holds regardless of which thread held the key (mission, eject,
evade, disengage, recovery) and regardless of the termination point, including
termination inside a press-and-release call. Every key any code path injects
shall be present in the cleanup release list.
<<<
RATIONALE: >>>
XTest key state lives in the X SERVER and survives the injecting process; a
key left held is auto-repeated into whatever window has focus, indefinitely.
Incident class: NOSE_DOWN/AFTERBURNER left pressed for the whole X session
after a mid-eject exit (pre-ADR 069 cleanup hardening), and the 2026-08-14
stuck-'i' incident (a test-suite mission thread outliving its keyboard stub —
CR-016-01). Enforced by Controller.cleanup()'s unconditional release of the
full injectable-key list (audit 2026-08-14 added the previously missing
'escape' and MISSION_J20_KEY), SIGTERM routing through the graceful path, and
stoppable daemon threads. The test suite carries its own session-end
release-all net in tests/conftest.py as defense in depth.
<<<

[REQUIREMENT]
UID: SAF-008
TITLE: Bounded climb hold
STATEMENT: >>>
A climb hold shall release all held flight keys unconditionally no later
than its duration cap — behavior_tree.climb.max_climb_s for a band-recovery
climb, behavior_tree.climb.mission_start_max_s for a mission-start climb —
after entry, and shall release them on mission cancellation, on program
exit, and on controller cleanup. Absence of fresh telemetry shall not end
the hold early, and shall not extend it past the cap.
<<<
RATIONALE: >>>
ADR 073 (3.2b/3.2c), mirroring SAF-006: an unreadable altitude (OCR dropout,
frozen frame) would otherwise pin nose-up and afterburner indefinitely — the
ADR 069 nose-hold-budget failure class. The cap firing without altitude
confirmation is logged at WARNING as a fault indicator. Enforced by the
climb thread's finally-block release, the stop event set in cleanup(), and
the mission prologue's cancellation path.
<<<

[REQUIREMENT]
UID: SAF-009
TITLE: Bounded respawn spawn-attitude hold
STATEMENT: >>>
A spawn-attitude guard hold shall release its held flight key
unconditionally no later than behavior_tree.climb.spawn_guard.max_hold_s
after entry, and shall release it on manual takeover, on eject or
missile-evade start, when the FSM leaves GAME_BATTLE, on program exit, and
on controller cleanup. When a climb hold is active at release time, the
guard shall skip the OS-level key release — the climb hold owns the key
state and its own release path applies.
<<<
RATIONALE: >>>
ADR 076. The guard holds NOSE_UP from death detection through the respawn
screen so the new life's first frames are already pitching up; while the
respawn screen is up the hold is inert, so the entire risk window is the
first seconds after spawn. The cap mirrors SAF-006/SAF-008: absence of the
alive handoff signal is a perception fault and is logged at WARNING. The
ownership rule prevents the guard's release from yanking a climb pitch
pulse in progress (two threads must never independently release the same
key).
<<<

[REQUIREMENT]
UID: SAF-010
TITLE: Tactic handoff leaves a flyable attitude
STATEMENT: >>>
A tactic that commands pitch shall not release its pitch input to neutral
while the observed flight-path angle is outside the flyable band bounded by
behavior_tree.climb.exit_pitch_deg. Before releasing it shall command the
aircraft back inside that band, subject to a bounded pulse budget, or hand
explicitly to a recovery tactic. Exhausting the budget shall release and be
logged as a fault indicator, not treated as success.
<<<
RATIONALE: >>>
ADR 086 d1. SAF-005 already bounds commanded nose-DOWN during an eject with
both a budget and an attitude-referenced release rule; SAF-008 bounds the
climb by DURATION only, and that missing half is a live defect. On
2026-08-21 the climb released all three flight keys at +73 degrees, leaving
the aircraft ballistic; it coasted 1500 m further, stalled at 24 KPH, fell
into an unrecovered dive and hit the ground with two missiles still racked.
84 climb completions in that session produced 21 near-vertical stalls.
Critically, SAF-008 and FR-007 were BOTH satisfied throughout — every
existing requirement describes the climb while it runs or when it starts,
none describes what it hands back. Currently unsatisfied by design; the
@relation marker lands with the ADR 086 implementation.
<<<

[REQUIREMENT]
UID: SAF-011
TITLE: Ground-collision avoidance by predicted time to ground
STATEMENT: >>>
While wingman is commanding flight in GAME_BATTLE and the aircraft is
descending, wingman shall command a recovery when the predicted time to
ground — altitude divided by descent rate — falls below
behavior_tree.climb.recover_below_time_s. When that predicted time is below
behavior_tree.climb.confirm_bypass_time_s the recovery shall fire on a
single qualifying reading rather than waiting for
behavior_tree.climb.confirm_reads confirmations. A rejected or absent
telemetry reading during an established descent shall not clear the descent
state for behavior_tree.climb.descent_memory_s.
<<<
RATIONALE: >>>
ADR 086 d2-d4. The existing recovery band is expressed in ALTITUDE, but the
emergency is governed by descent RATE: at the 552 m/s descent measured on
2026-08-21 the 4000 m sustain band allowed 7.2 s and the 500 m emergency
band allowed 0.9 s, while telemetry ticks about every 3 s and confirm_reads
of 2 needs roughly 6 s — the confirmation was slower than the margin it
protected, so the band could not fire at any altitude tuning. The band was
also frozen: make_climb_condition holds its decision when altitude is None,
and rapid altitude change is exactly what trips the ADR 038/067
plausibility filter, so the net went deaf precisely when needed. Absence of
perception must not read as absence of danger. Currently unsatisfied by
design; the @relation marker lands with the ADR 086 implementation.
<<<

[REQUIREMENT]
UID: SAF-012
TITLE: No terrain impact while the airframe is serviceable
STATEMENT: >>>
Wingman shall not fly the aircraft into terrain while it is commanding
flight and the airframe remains serviceable. A ground impact that is not
the intended conclusion of an eject sequence is a violation. Verification
is by outcome over a session: near-vertical stalls, counted as telemetry
samples at or above +80 degrees flight-path angle with speed below 120 KPH,
and ground impacts occurring while missiles remain available.
<<<
RATIONALE: >>>
ADR 086. Modelled on FR-005, which is likewise verified by outcome rather
than by mechanism because no in-game sensor reports the property directly.
This requirement is the standing statement of the hazard that SAF-010 and
SAF-011 address by different means, and it is what stays true if either
mechanism is later replaced. Baseline for comparison, session
2026-08-21 04:16: 21 near-vertical stalls across 84 climb completions and
51 respawns over 16 missions (3.2 per mission), against 53 missiles-empty
ejects. The eject share is by design and is expected to be unchanged; the
stall share is the target. Currently unsatisfied by design.
<<<

[REQUIREMENT]
UID: SAF-013
TITLE: Thrust is not withdrawn during an active missile threat
STATEMENT: >>>
While an incoming-missile alert is detected and wingman is commanding flight,
no fuel-conservation or altitude-management policy shall release the
afterburner. This overrides the reserve floor and the at-target thrust cut.
The sole exception is an afterburner fuel reading of zero, where the control
produces no thrust and holding it prevents the recharge that a subsequent
evade depends on.
<<<
RATIONALE: >>>
ADR 088 d2. ADR 075 releases the burner at a reserve floor to keep fuel for a
FUTURE evade; ADR 083 d3 cuts it at target altitude to stop a zoom climb
stalling itself. Both are correct in the situations they were written for, and
neither considered an evade already in progress — an evade in hand is worth
more than a hypothetical one. Observed 2026-08-22 01:47:39: the ADR 070 d12
manoeuvre limit released the evade with the alert still present, the climb
tactic took selection, and the burner was cut 1.7 seconds later while a
missile was tracking. The zero-fuel exception is physical rather than
policy-based and is why this is stated as an override of specific policies
rather than as an unconditional hold.
<<<

[REQUIREMENT]
UID: SAF-014
TITLE: Exactly one wingman instance commands the aircraft
STATEMENT: >>>
At most one wingman process shall command the aircraft at a time. A wingman
process that starts while another is already running shall command nothing —
no key injection, no mouse injection — and shall report the refusal.
<<<
RATIONALE: >>>
This is a PRECONDITION for the guarantees the other safety requirements make,
not an independent property. Every one of them is written about "wingman" as a
single agent: SAF-001 says commanded flight ceases within 2.0 s of an operator
input, SAF-006/007/009/010 bound a hold, SAF-008 releases every injected key on
exit. A second instance is outside the first instance's stop events, mission
lock, tactic holds and cleanup, so each of those guarantees is silently void
while two are running — instance A ceases and instance B does not.

Observed 2026-08-30: two instances ran concurrently for over an hour, both
injecting into the same nested display. A manual takeover in one left the other
still commanding the aircraft, which the operator experienced as inputs
fighting their own. Nothing in either log indicated a fault, because each
instance was behaving correctly in isolation — the failure exists only between
them, and neither is positioned to detect it.

Enforced by an abstract Unix socket claimed in main() before the injection
display, capture or controller are set up. Abstract rather than a PID file
because the kernel releases the name however the process dies, so a SIGKILLed
instance leaves no stale lock — the case that would otherwise prevent wingman
starting at all, which is the more dangerous failure of the two.
<<<

[REQUIREMENT]
UID: SAF-015
TITLE: A termination trigger bounds total time to exit, whether or not the main loop notices it
STATEMENT: >>>
Following any termination trigger — SIGTERM, SIGHUP, or the operator's second
Backspace — wingman shall exit within a bounded time even if the main loop's
`exit_requested` check never observes the trigger. The bound applies from the
moment the OS or the operator delivers the trigger, not from the moment
`exit_requested` is observed set, so a trigger that is silently absorbed
before reaching that check is still covered.
<<<
RATIONALE: >>>
ADR 121 D1 already bounds cleanup once it starts: a watchdog armed in the
`finally:` block forces exit if cleanup stalls past 90 s. That protects
everything AFTER the main loop breaks out of `while True:`, which requires
`exit_requested.is_set()` to have been observed true at the top of some tick.
It does not protect the step before that — the trigger actually causing
`exit_requested` to become true in the first place.

Observed 2026-09-11: SIGTERM sent directly to the interpreter PID (confirmed
via `ps`, not the `uv run` shim) produced no effect for 75+ seconds on a
process that was, throughout, fully healthy and ticking at its normal ~1 s
cadence — not stuck, not stalled, just never noticing. No `Exit requested`
log line, no `SHUTDOWN WATCHDOG` line, because the watchdog structurally
cannot arm for a signal that never reaches the code that arms it. Ended in a
manual SIGKILL. This is distinct from, and not covered by, either the
original 2026-09-05 hang (D1-D5) or the 2026-09-08 SIGHUP gap (both of which
assumed the trigger would at least be noticed, eventually, if not acted on
cleanly) — see ADR 121, "SIGTERM had no effect at all on a live, ticking
process."

Enforced by `_arm_signal_ack_watchdog`, armed from inside the SIGTERM/SIGHUP
handlers themselves at the instant `exit_requested.set()` runs, independent
of `_arm_shutdown_watchdog`'s existing 90 s cleanup-stall guard; the operator's
second Backspace is covered by that existing 90 s guard directly, since its
own detection loop polls reliably and was never the silent-absorption risk
SIGTERM/SIGHUP had. It does not cover a signal that never reaches the handler
at all — see ADR 121's 2026-09-11 addendum for what is and is not closed by
this, and why that gap may still be live.

A same-day code review of the first cut found this enforcement was itself
incomplete: STANDBY — an intentional, unbounded, operator-controlled wait
that never checks `exit_requested` — did not cancel the signal-ack watchdog
on entry, so a SIGTERM/SIGHUP arriving while parked there would have violated
SAF-010 (the operator's manual-flight handback) by force-exiting the session
regardless. Fixed the same day; see ADR 121's "Code review caught two
regressions before they shipped live" section for this and a second,
narrower repeat-signal gap found and fixed alongside it.
<<<
